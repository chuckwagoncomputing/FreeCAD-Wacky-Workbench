import unittest
import sys
import Test
import FreeCAD
import Part
import PartDesign
import PartDesignGui
import Sketcher
import StraightCut
import Asm4_libs as Asm4
import newAssemblyCmd
import newDatumCmd
import insertLinkCmd
import placeLinkCmd

status = 0

def setUpBodyTool(doc):
	b2 = doc.addObject('PartDesign::Body','Body001')
	b2.Label = 'Body'
	s2 = b2.newObject('Sketcher::SketchObject','Sketch001')
	pln = [o for o in b2.Origin.OutList if o.isDerivedFrom('App::Plane') and o.Placement.Rotation.isSame(App.Rotation(0,0,0,1), 1e-15)][0]
	s2.Support = (pln,[''])
	s2.MapMode = 'FlatFace'
	s2.addGeometry(Part.Circle(App.Vector(0.000000,0.000000,0),App.Vector(0,0,1),17.323547),False)
	s2.addConstraint(Sketcher.Constraint('Coincident',0,3,-1,1))
	p2 = b2.newObject('PartDesign::Pad','Pad001')
	p2.Profile = s2
	p2.Length = 10
	p2.ReferenceAxis = (s2,['N_Axis'])
	p2.Length = 60.000000
	doc.recompute()
	return b2

def setUpBodyBase(doc):
	b1 = doc.addObject('PartDesign::Body','Body')
	b1.Label = 'Body'
	s1 = b1.newObject('Sketcher::SketchObject','Sketch')
	pln = [o for o in b1.Origin.OutList if o.isDerivedFrom('App::Plane') and o.Placement.Rotation.isSame(App.Rotation(0,0,0,1), 1e-15)][0]
	s1.Support = (pln,[''])
	s1.MapMode = 'FlatFace'
	geoList = []
	geoList.append(Part.LineSegment(App.Vector(0.000000,0.000000,0),App.Vector(110.933342,0.000000,0)))
	geoList.append(Part.LineSegment(App.Vector(110.933342,0.000000,0),App.Vector(110.933342,88.985420,0)))
	geoList.append(Part.LineSegment(App.Vector(110.933342,88.985420,0),App.Vector(0.000000,88.985420,0)))
	geoList.append(Part.LineSegment(App.Vector(0.000000,88.985420,0),App.Vector(0.000000,0.000000,0)))
	s1.addGeometry(geoList,False)
	conList = []
	conList.append(Sketcher.Constraint('Coincident',0,1,-1,1))
	conList.append(Sketcher.Constraint('Coincident',0,2,1,1))
	conList.append(Sketcher.Constraint('Coincident',1,2,2,1))
	conList.append(Sketcher.Constraint('Coincident',2,2,3,1))
	conList.append(Sketcher.Constraint('Coincident',3,2,0,1))
	conList.append(Sketcher.Constraint('Horizontal',0))
	conList.append(Sketcher.Constraint('Horizontal',2))
	conList.append(Sketcher.Constraint('Vertical',1))
	conList.append(Sketcher.Constraint('Vertical',3))
	s1.addConstraint(conList)
	del geoList, conList
	p1 = b1.newObject('PartDesign::Pad','Pad')
	p1.Profile = s1
	p1.Length = 10
	p1.ReferenceAxis = (s1,['N_Axis'])
	p1.Length = 10.000000
	doc.recompute()
	return b1

def setUpPartBase(doc):
	b1 = doc.addObject("Part::Box","Box")
	b1.Label = "Cube"
	doc.recompute()
	b1.Length='100.00 mm'
	b1.Width='100.00 mm'
	b1.Height='10.00 mm'
	return b1

def setUpPartTool(doc):
	b2 = doc.addObject("Part::Cylinder","Cylinder")
	b2.Label = "Cylinder"
	doc.recompute()
	b2.Radius='10.00 mm'
	b2.Height='50.00 mm'
	b2.Angle='360.00 °'
	b2.FirstAngle='0.00 °'
	b2.SecondAngle='0.00 °'
	return b2

def addLCS(b, n):
	c = b.newObject('PartDesign::CoordinateSystem', n)
	c.Support = [(b.Origin.OriginFeatures[0],'')]
	c.MapMode = 'ObjectXY'
	return c

def addLink(p, n, a, o, c):
	l = Asm4.getAssembly().newObject('App::Link', n)
	l.LinkedObject = p
	Asm4.makeAsmProperties(l)
	l.AttachedBy = '#' + c
	l.AttachedTo = a + '#' + o
	l.SolverId = 'Asm4EE'
	expr = Asm4.makeExpressionPart(a, None, o, "Unnamed", c )
	l.setExpression('Placement', expr)
	return l

def setUpStdPart(doc):
	p1 = doc.addObject('App::Part', "Part")
	p1.Label = "Part"
	doc.getObject('Parts').addObject(p1)
	return p1

class TestStraightCut(unittest.TestCase):
	def tearDown(self):
		global status
		if hasattr(self._outcome, 'errors'):
			result = self.defaultTestResult()
			self._feedErrorsToResult(result, self._outcome.errors)
		else:
			result = self._outcome.result
		ok = all(test != self for test, text in result.errors + result.failures)
		if ok:
			print('\nOK: %s' % (self.id(),))
		else:
			status = 1
		for typ, errors in (('ERROR', result.errors), ('FAIL', result.failures)):
			for test, text in errors:
				if test is self:
					msg = [x for x in text.split('\n')[1:]
						if not x.startswith(' ')][0]
					App.Console.PrintMessage("\n\n%s: %s\n     %s" % (typ, self.id(), msg))

	def test_positioned_tool(self):
		doc = App.newDocument()
		b1 = setUpBodyBase(doc)
		b2 = setUpBodyTool(doc)
		b2.Placement = App.Placement(App.Vector(35,50,-20),App.Rotation(App.Vector(15,30,1),45))
		doc.recompute()
		Gui.Selection.addSelection('Unnamed','Body')
		Gui.ActiveDocument.ActiveView.setActiveObject('pdbody',b1)
		Gui.Selection.addSelection('Unnamed','Body001')
		Gui.activateWorkbench("WackyWorkbench")
		Gui.runCommand('StraightCut',0)
		doc.recompute()
		v = b1.Shape.Volume
		App.closeDocument(doc.Name)
		self.assertAlmostEqual(v, 81923.91622644056, 7)

	def test_positioned_base(self):
		doc = App.newDocument()
		b1 = setUpBodyBase(doc)
		b2 = setUpBodyTool(doc)
		b1.Placement = App.Placement(App.Vector(-35,-50,25),App.Rotation(App.Vector(15,30,1),45))
		doc.recompute()
		Gui.Selection.addSelection('Unnamed','Body')
		Gui.ActiveDocument.ActiveView.setActiveObject('pdbody',b1)
		Gui.Selection.addSelection('Unnamed','Body001')
		Gui.activateWorkbench("WackyWorkbench")
		Gui.runCommand('StraightCut',0)
		doc.recompute()
		v = b1.Shape.Volume
		App.closeDocument(doc.Name)
		self.assertAlmostEqual(v, 82077.27162062649, 7)

	def test_positioned_both(self):
		doc = App.newDocument()
		b1 = setUpBodyBase(doc)
		b2 = setUpBodyTool(doc)
		b1.Placement = App.Placement(App.Vector(10,10,0),App.Rotation(App.Vector(0,0,1),0))
		b2.Placement = App.Placement(App.Vector(35,50,-20),App.Rotation(App.Vector(15,30,1),45))
		doc.recompute()
		Gui.Selection.addSelection('Unnamed','Body')
		Gui.ActiveDocument.ActiveView.setActiveObject('pdbody',b1)
		Gui.Selection.addSelection('Unnamed','Body001')
		Gui.activateWorkbench("WackyWorkbench")
		Gui.runCommand('StraightCut',0)
		doc.recompute()
		v = b1.Shape.Volume
		App.closeDocument(doc.Name)
		self.assertAlmostEqual(v, 81923.91622644138, 7)

	def test_features_positioned_both(self):
		doc = App.newDocument()
		b1 = setUpBodyBase(doc)
		b2 = setUpBodyTool(doc)
		b1.Placement = App.Placement(App.Vector(10,10,0),App.Rotation(App.Vector(0,0,1),0))
		b2.Placement = App.Placement(App.Vector(35,50,-20),App.Rotation(App.Vector(15,30,1),45))
		doc.recompute()
		Gui.Selection.addSelection('Unnamed','Pad')
		Gui.ActiveDocument.ActiveView.setActiveObject('pdbody',b1)
		Gui.Selection.addSelection('Unnamed','Pad001')
		Gui.activateWorkbench("WackyWorkbench")
		Gui.runCommand('StraightCut',0)
		doc.recompute()
		v = b1.Shape.Volume
		App.closeDocument(doc.Name)
		self.assertAlmostEqual(v, 81923.91622644138, 7)

	def test_assembly_tool(self):
		doc = App.newDocument()
		b1 = setUpBodyBase(doc)
		b2 = setUpBodyTool(doc)
		Gui.activateWorkbench("Assembly4Workbench")
		Gui.runCommand('Asm4_newAssembly',0)
		c1 = addLCS(b1, 'LCS1')
		c2 = addLCS(b1, 'LCS2')
		c2.AttachmentOffset = App.Placement(App.Vector(50, 30, -25),  App.Rotation(0, 20, 30))
		c3 = addLCS(b2, 'LCS3')
		l1 = addLink(b1, 'Base', 'Parent Assembly', 'LCS_Origin', 'LCS1')
		l2 = addLink(b2, 'Tool', 'Base', 'LCS2', 'LCS3')
		Gui.Selection.clearSelection()
		Gui.Selection.addSelection('Unnamed','Assembly','Base.')
		Gui.Selection.addSelection('Unnamed','Assembly','Tool.')
		Gui.activateWorkbench("WackyWorkbench")
		Gui.runCommand('StraightCut',0)
		doc.recompute()
		v = b1.Shape.Volume
		App.closeDocument(doc.Name)
		self.assertAlmostEqual(v, 87457.9652414781, 7)

	def test_assembly_base(self):
		doc = App.newDocument()
		b1 = setUpBodyBase(doc)
		b2 = setUpBodyTool(doc)
		Gui.activateWorkbench("Assembly4Workbench")
		Gui.runCommand('Asm4_newAssembly',0)
		c1 = addLCS(b1, 'LCS1')
		c2 = addLCS(b1, 'LCS2')
		c2.AttachmentOffset = App.Placement(App.Vector(50, 30, -25),  App.Rotation(0, 20, 30))
		c3 = addLCS(b2, 'LCS3')
		l1 = addLink(b2, 'Tool', 'Parent Assembly', 'LCS_Origin', 'LCS3')
		l1 = addLink(b1, 'Base', 'Tool', 'LCS3', 'LCS2')
		Gui.Selection.clearSelection()
		Gui.Selection.addSelection('Unnamed','Assembly','Base.')
		Gui.Selection.addSelection('Unnamed','Assembly','Tool.')
		Gui.activateWorkbench("WackyWorkbench")
		Gui.runCommand('StraightCut',0)
		doc.recompute()
		v = b1.Shape.Volume
		App.closeDocument(doc.Name)
		self.assertAlmostEqual(v, 87457.96524147251, 7)

	def test_part_positioned_base(self):
		doc = App.newDocument()
		b1 = setUpPartBase(doc)
		b2 = setUpPartTool(doc)
		b2.Placement = App.Placement(App.Vector(45.00,50.00,-15.00),App.Rotation(App.Vector(0.90,-0.40,0.10),45.00))
		doc.recompute()
		Gui.Selection.clearSelection()
		Gui.Selection.addSelection('Unnamed','Box')
		Gui.Selection.addSelection('Unnamed','Cylinder')
		Gui.activateWorkbench("WackyWorkbench")
		Gui.runCommand('StraightCut',0)
		doc.recompute()
		v = doc.getObject("StraightCut").Shape.Volume
		App.closeDocument(doc.Name)
		self.assertAlmostEqual(v, 93592.68786834327, 7)

	def test_part_positioned_tool(self):
		doc = App.newDocument()
		b1 = setUpPartBase(doc)
		b2 = setUpPartTool(doc)
		b1.Placement = App.Placement(App.Vector(-45.00,-50.00,-45.00),App.Rotation(App.Vector(0.90,-0.40,0.10),45.00))
		doc.recompute()
		Gui.Selection.clearSelection()
		Gui.Selection.addSelection('Unnamed','Box')
		Gui.Selection.addSelection('Unnamed','Cylinder')
		Gui.activateWorkbench("WackyWorkbench")
		Gui.runCommand('StraightCut',0)
		doc.recompute()
		v = doc.getObject("StraightCut").Shape.Volume
		App.closeDocument(doc.Name)
		self.assertAlmostEqual(v, 93592.68786813301, 7)

	def test_mixed_part_body(self):
		doc = App.newDocument()
		b1 = setUpBodyBase(doc)
		b2 = setUpPartTool(doc)
		b2.Placement = App.Placement(App.Vector(35,50,-20),App.Rotation(App.Vector(15,30,1),45))
		doc.recompute()
		Gui.Selection.addSelection('Unnamed','Body')
		Gui.ActiveDocument.ActiveView.setActiveObject('pdbody',b1)
		Gui.Selection.addSelection('Unnamed','Cylinder')
		Gui.activateWorkbench("WackyWorkbench")
		Gui.runCommand('StraightCut',0)
		doc.recompute()
		v = b1.Shape.Volume
		App.closeDocument(doc.Name)
		self.assertAlmostEqual(v, 92426.03185588072, 7)

	def test_mixed_body_part(self):
		doc = App.newDocument()
		b1 = setUpPartBase(doc)
		b2 = setUpBodyTool(doc)
		b2.Placement = App.Placement(App.Vector(35,50,-20),App.Rotation(App.Vector(15,30,1),45))
		doc.recompute()
		Gui.Selection.addSelection('Unnamed','Box')
		Gui.ActiveDocument.ActiveView.setActiveObject('pdbody',b1)
		Gui.Selection.addSelection('Unnamed','Body001')
		Gui.activateWorkbench("WackyWorkbench")
		Gui.runCommand('StraightCut',0)
		doc.recompute()
		v = doc.getObject("StraightCut").Shape.Volume
		App.closeDocument(doc.Name)
		self.assertAlmostEqual(v, 83209.41592770607, 7)

	def test_mixed_body_feature(self):
		doc = App.newDocument()
		b1 = setUpBodyBase(doc)
		b2 = setUpBodyTool(doc)
		b1.Placement = App.Placement(App.Vector(10,10,0),App.Rotation(App.Vector(0,0,1),0))
		b2.Placement = App.Placement(App.Vector(35,50,-20),App.Rotation(App.Vector(15,30,1),45))
		doc.recompute()
		Gui.Selection.addSelection('Unnamed','Body')
		Gui.ActiveDocument.ActiveView.setActiveObject('pdbody',b1)
		Gui.Selection.addSelection('Unnamed','Pad001')
		Gui.activateWorkbench("WackyWorkbench")
		Gui.runCommand('StraightCut',0)
		doc.recompute()
		v = b1.Shape.Volume
		App.closeDocument(doc.Name)
		self.assertAlmostEqual(v, 81923.91622644138, 7)

	def test_mixed_feature_body(self):
		doc = App.newDocument()
		b1 = setUpBodyBase(doc)
		b2 = setUpBodyTool(doc)
		b1.Placement = App.Placement(App.Vector(10,10,0),App.Rotation(App.Vector(0,0,1),0))
		b2.Placement = App.Placement(App.Vector(35,50,-20),App.Rotation(App.Vector(15,30,1),45))
		doc.recompute()
		Gui.Selection.addSelection('Unnamed','Pad')
		Gui.ActiveDocument.ActiveView.setActiveObject('pdbody',b1)
		Gui.Selection.addSelection('Unnamed','Body001')
		Gui.activateWorkbench("WackyWorkbench")
		Gui.runCommand('StraightCut',0)
		doc.recompute()
		v = b1.Shape.Volume
		App.closeDocument(doc.Name)
		self.assertAlmostEqual(v, 81923.91622644138, 7)

	def test_stdpart_body(self):
		doc = App.newDocument()
		Gui.activateWorkbench("Assembly4Workbench")
		Gui.runCommand('Asm4_newAssembly',0)
		p1 = setUpStdPart(doc)
		p2 = setUpStdPart(doc)
		b1 = setUpBodyBase(doc)
		b2 = setUpBodyTool(doc)
		p1.addObject(b1)
		p2.addObject(b2)
		c1 = addLCS(p1, 'LCS1')
		c2 = addLCS(p1, 'LCS2')
		c2.AttachmentOffset = App.Placement(App.Vector(50, 30, -25),  App.Rotation(0, 20, 30))
		c3 = addLCS(p2, 'LCS3')
		l1 = addLink(p1, 'Base', 'Parent Assembly', 'LCS_Origin', 'LCS1')
		l2 = addLink(p2, 'Tool', 'Base', 'LCS2', 'LCS3')
		Gui.Selection.clearSelection()
		Gui.Selection.addSelection('Unnamed','Assembly','Base.Body.')
		Gui.Selection.addSelection('Unnamed','Assembly','Tool.Body001.')
		Gui.activateWorkbench("WackyWorkbench")
		Gui.runCommand('StraightCut',0)
		doc.recompute()
		v = b1.Shape.Volume
		App.closeDocument(doc.Name)
		self.assertAlmostEqual(v, 87457.9652414781, 7)


Test.runTestsFromClass(TestStraightCut)
exit(status)
